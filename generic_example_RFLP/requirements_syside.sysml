package 'Requirements Example' {
  requirement def 'RQ-01' {
    doc
    /* The fridge shall maintain an internal temperature between 1°C and 4°C (34°F and 39°F) for food preservation. */
  }
  requirement def 'RQ-02' {
    doc
    /* The freezer compartment shall maintain a temperature of -18°C (0°F) or below for long-term storage of frozen items. */
  }
  requirement def 'RQ-03' {
    doc
    /* The fridge shall meet or exceed Energy Star efficiency standards, consuming no more than 400 kWh per year. */
  }
  requirement def 'RQ-04' {
    doc
    /* The fridge shall have an automatic defrosting system to prevent the buildup of frost inside the freezer. */
  }
  requirement def 'RQ-05' {
    doc
    /* The fridge doors shall have magnetic gaskets to ensure an airtight seal and prevent energy loss. */
  }
  requirement def 'RQ-06' {
    doc
    /* The operational noise of the fridge shall not exceed 40 dB(A) under normal conditions. */
  }
  requirement def 'RQ-07' {
    doc
    /* The fridge shall provide adjustable shelves to accommodate a variety of food sizes and configurations. */
  }
  requirement def 'RQ-08' {
    doc
    /* The fridge shall include a digital temperature control system with an accuracy of ±1°C. */
  }
  requirement def 'RQ-09' {
    doc
    /* The fridge shall feature a humidity-controlled drawer to extend the freshness of perishable items like fruits and vegetables. */
  }
  requirement def 'RQ-10' {
    doc
    /* The fridge shall be equipped with energy-efficient LED lighting that illuminates all compartments. */
  }
  requirement def 'RQ-11' {
    doc
    /* The fridge shall have a built-in water and ice dispenser capable of dispensing both cubed and crushed ice. */
  }
  requirement def 'RQ-12' {
    doc
    /* The fridge shall support Wi-Fi connectivity, enabling remote temperature monitoring and control via a mobile app. */
  }
  requirement def 'RQ-13' {
    doc
    /* The fridge shall include an audible alarm system to notify users if the door is left open for more than 2 minutes. */
  }
  requirement def 'RQ-14' {
    doc
    /* The fridge shall provide a minimum storage capacity of 20 cubic feet, including separate compartments for dairy, meat, and produce. */
  }
  requirement def 'RQ-15' {
    doc
    /* The fridge shall include a backup battery or auxiliary power system capable of maintaining critical temperatures for at least 4 hours during a power outage. */
  }
}
