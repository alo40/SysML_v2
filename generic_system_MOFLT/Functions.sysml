package Functions {
    action request_function {
        action detect_hmi_activation;
        action evaluate_hmi_status;
        action monitor_hmi_status;
        action provide_power_supply;
        action send_hmi_status;
    }
}
